# -*- coding: utf-8 -*-

# Macro Begin: /home/harryvl/fcFEM/Source_Code/Test2_Macro.FCMacro +++++++++++++++++++++++++++++++++++++++++++++++++
import FreeCAD

# Gui.runCommand('Std_DlgMacroRecord',0)
### Begin command Std_Workbench
# Gui.activateWorkbench("PartWorkbench")
### End command Std_Workbench
### Begin command Std_Workbench
# Gui.activateWorkbench("FemWorkbench")
### End command Std_Workbench
### Begin command Std_Workbench
# Gui.activateWorkbench("PartWorkbench")
### End command Std_Workbench
# with open('/snap/freecad/140/usr/share/Mod/Start/StartPage/LoadNew.py') as file:
# 	exec(file.read())
# App.setActiveDocument("Unnamed")
# App.ActiveDocument=App.getDocument("Unnamed")
# Gui.ActiveDocument=Gui.getDocument("Unnamed")
### Begin command Part_Box
App.ActiveDocument.addObject("Part::Box","Box")
App.ActiveDocument.ActiveObject.Label = "Cube"
# Object created at document root.
App.ActiveDocument.recompute()
# Gui.SendMsgToActiveView("ViewFit")
### End command Part_Box
### Begin command Std_Workbench
# Gui.activateWorkbench("FemWorkbench")
### End command Std_Workbench
### Begin command FEM_Analysis
ObjectsFem.makeAnalysis(FreeCAD.ActiveDocument, 'Analysis')
FemGui.setActiveAnalysis(FreeCAD.ActiveDocument.ActiveObject)
ObjectsFem.makeSolverCalculixCcxTools(FreeCAD.ActiveDocument)
FemGui.getActiveAnalysis().addObject(FreeCAD.ActiveDocument.ActiveObject)
### End command FEM_Analysis
# Gui.Selection.addSelection('Unnamed','Box')
### Begin command FEM_MeshGmshFromShape
ObjectsFem.makeMeshGmsh(FreeCAD.ActiveDocument, 'FEMMeshGmsh')
FreeCAD.ActiveDocument.ActiveObject.Part = FreeCAD.ActiveDocument.Box
FemGui.getActiveAnalysis().addObject(FreeCAD.ActiveDocument.ActiveObject)
FreeCADGui.ActiveDocument.setEdit(FreeCAD.ActiveDocument.ActiveObject.Name)
### End command FEM_MeshGmshFromShape
# Gui.Selection.clearSelection()
# Gui.Selection.addSelection('Unnamed','FEMMeshGmsh')
# Gui.runCommand('Std_ToggleVisibility',0)
### Begin command FEM_ConstraintPressure
App.activeDocument().addObject("Fem::ConstraintPressure","ConstraintPressure")
App.activeDocument().ConstraintPressure.Pressure = 1000.0
App.activeDocument().ConstraintPressure.Reversed = False
App.activeDocument().ConstraintPressure.Scale = 1
App.activeDocument().Analysis.addObject(App.activeDocument().ConstraintPressure)
for amesh in App.activeDocument().Objects:
    if "ConstraintPressure" == amesh.Name:
        amesh.ViewObject.Visibility = True
    elif "Mesh" in amesh.TypeId:
        aparttoshow = amesh.Name.replace("_Mesh","")
        for apart in App.activeDocument().Objects:
            if aparttoshow == apart.Name:
                apart.ViewObject.Visibility = True
        amesh.ViewObject.Visibility = False

App.ActiveDocument.recompute()
# Gui.activeDocument().setEdit('ConstraintPressure')
### End command FEM_ConstraintPressure
# Gui.Selection.clearSelection()
# Gui.Selection.addSelection('Unnamed','Box','Face6',7.12137,7.37293,10)
App.ActiveDocument.ConstraintPressure.Pressure = 1000.000000
App.ActiveDocument.ConstraintPressure.Reversed = False
App.ActiveDocument.ConstraintPressure.Scale = 1
App.ActiveDocument.ConstraintPressure.References = [(App.ActiveDocument.Box,"Face6")]
App.ActiveDocument.recompute()
# Gui.activeDocument().resetEdit()
# Gui.Selection.clearSelection()
### Begin command FEM_ConstraintFixed
App.activeDocument().addObject("Fem::ConstraintFixed","ConstraintFixed")
App.activeDocument().ConstraintFixed.Scale = 1
App.activeDocument().Analysis.addObject(App.activeDocument().ConstraintFixed)
for amesh in App.activeDocument().Objects:
    if "ConstraintFixed" == amesh.Name:
        amesh.ViewObject.Visibility = True
    elif "Mesh" in amesh.TypeId:
        aparttoshow = amesh.Name.replace("_Mesh","")
        for apart in App.activeDocument().Objects:
            if aparttoshow == apart.Name:
                apart.ViewObject.Visibility = True
        amesh.ViewObject.Visibility = False

App.ActiveDocument.recompute()
# Gui.activeDocument().setEdit('ConstraintFixed')
### End command FEM_ConstraintFixed
# Gui.Selection.addSelection('Unnamed','Box','Face5',7.93289,2.48665,2.22045e-16)
# Gui.Selection.clearSelection()
# Gui.Selection.addSelection('Unnamed','Box','Face5',8.79888,1.68389,0)
App.ActiveDocument.ConstraintFixed.Scale = 1
App.ActiveDocument.ConstraintFixed.References = [(App.ActiveDocument.Box,"Face5")]
App.ActiveDocument.recompute()
# Gui.activeDocument().resetEdit()
# Gui.Selection.clearSelection()
### Begin command FEM_MaterialSolid
FemGui.getActiveAnalysis().addObject(ObjectsFem.makeMaterialSolid(FreeCAD.ActiveDocument))
FreeCADGui.ActiveDocument.setEdit(FreeCAD.ActiveDocument.ActiveObject.Name)
### End command FEM_MaterialSolid
# Gui.Selection.addSelection('Unnamed','Box','Face3',4.85686,1.33227e-15,7.13456)
# Macro End: /home/harryvl/fcFEM/Source_Code/Test2_Macro.FCMacro +++++++++++++++++++++++++++++++++++++++++++++++++
